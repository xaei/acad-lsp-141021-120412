(defun c:note_settings()
	(command "_layer" "lweight" "0.13" "*A-ANNO-NOTE*" "")
)
(defun c:nonplot_settings () 
	(command "layer" "plot" "no" "*NonPlot*" "")
	(command "_layer" "freeze" "*NonPlot*" "")
	(command "_layer" "thaw" "*24x36|NonPlot*" "")
	(command "_layer" "thaw" "NonPlot" "")
)
(defun c:grids_on()
	(command "_layer" "thaw" "*A-GRID-PLAN-*" "")
	)
(defun c:stb_settings () 
	(command "_layer" "pstyle" "Solid" "*" "")
	(command "_layer" "pstyle" "Normal" "*NonPlot*,*Viewport*" "")
	(command "_layer" "pstyle" "Normal" "*WIPE*" "")
)
(defun c:ssr () (command "select" "previous" "") (prin1))
(defun c:frr () (command "draworder" "front") (prin1))
(defun c:baa () (command "draworder" "back") (prin1))
(defun c:xra () (command "xref" "reload" "*") (prin1))
(defun c:xrf () (command "_layer" "freeze" "*xref*" ""))
(defun c:xrt () (command "_layer" "thaw" "*xref*" ""))
(defun c:ww ()
	(if (= (getvar "LWDISPLAY") 1) (setvar "LWDISPLAY" 0) (setvar "LWDISPLAY" 1))
)
(defun c:demoOff () (command "_layer" "freeze" "*A-DEMO*" "") (princ "not demo!") )
(defun c:npr_off () 
	(command "_layer" "freeze" "*NonPlot*" "")
	(command "_layer" "thaw" "NonPlot" "")
	(princ "NP!")
)
(defun c:areaOff () 
	(command "_layer" "freeze" "*AREA*,*Area*" "")
	(princ "AREAOFF!")
)
(defun c:saveclose () 
	(command "._save" "")
	(princ (car(layoutlist)))
	(command "._close" "")
)
(defun c:REL() (load "startup.lsp") (prin1))
;(defun c:BYL() (command "._chprop" (ssget) "Color" "ByLayer" "Lineweight" "ByLayer" "LineType" "ByLayer" "") )
(defun c:byl ()
  (setq ss1 (ssget))
  (command "change" ss1 "" "p" "Color" "ByLayer" "LWeight" "ByLayer" "Ltype" "ByLayer" "PlotStyle" "ByLayer" "")
  )
(defun c:bylall ()
  (setq setOfAll1 (ssget "x"));
  (command "change" setOfAll1 "" "p" "Color" "ByLayer" "LWeight" "ByLayer" "Ltype" "ByLayer" "PlotStyle" "ByLayer" "")
  )
(defun c:cor () (command "._copybase" "0,0" (ssget) ""))
(princ "cor loaded")
(defun c:por () (command "._pasteclip" "0,0"))
(princ "por loaded")
(defun c:xrr ()
	(command "._xref" "pathType" "*" "relative")
	(princ "RELATIVE!")
)
(defun c:bsl()
	(setvar "cmdecho" 0)
	(command "_bedit");
	(setq setOfAll1 (ssget "x"));
	(c:bylall)
	(command "._bsave")
	(command "._bclose")
	(setvar "cmdecho" 1);
);
(defun c:s1()
	(setvar "cmdecho" 0)
	(command "_model");
	(princ "modeling!!\n");
	(setq setOfAll1 (ssget "x"));
	(princ setOfAll1)(princ "\n");
	(command "._copybase" "0,0" setOfAll1 "")(princ "modelspace copied\n");
	(setvar "cmdecho" 1);
	(command "_zoom" "a")
);
(defun c:s2()
	(setvar 'ctab (car(layoutlist)))
	(setq setOfAll2 (ssget "x"))
	(command "._copybase" "0,0" setOfAll2 "")(princ "paperspace1 copied\n");
	(princ (car(layoutlist)))
	(command "_zoom" "a")
)
(defun c:d1()
	(setvar "cmdecho" 0)
	(command "_model");
	(command "._pasteclip" "0,0");
	(princ "pasted model")
	(setvar "cmdecho" 1);
	(command "_zoom" "a")
);
(defun c:d2()
	(setvar 'ctab (car(layoutlist)))
	(command "._pasteclip" "0,0")
	(princ "pasted paper1")
	(command "_zoom" "a")
)
(defun c:floorPatt()
	(setq linelist '(("DOT10" . "acad2.lin")))
	(princ "patt will be ")(princ linelist)
	(foreach lin linelist
		(if (tblsearch "LTYPE" (car lin))
			(command "_linetype" "_load" (car lin) (cdr lin) "_yes" "")
			(command "-linetype" "_load" (car lin) (cdr lin) "")
		)
	)
	(command "_layer" "ltype" "DOT10" "*A-FLOR-PATT*" "")
)
(load "lsp/LayerStates-1_2.fas" "failed loading layerstates")
(load "lsp/sel.lsp" "failed loading SEL")
(load "lsp/demoPlansSettingsv0.lsp" "failed loading DPS")
(load "lsp/wallSettingsv0.lsp" "failed loading wallSettingsv0")
(load "lsp/rcpSettingsv0.lsp" "failed loading rcpSettingsv0")
(load "lsp/colorSettingsv0.lsp" "failed loading colorSettingsv0")
(load "lsp/exstRenamev0.lsp" "failed loading exstRenamev0")
; (if s::startup
;  (setq s::startup (append s::startup (command "WSCURRENT" "MyWorkspace")))
;  (defun s::startup () (command "WSCURRENT" "MyWorkspace"))
; )
(command "POLARANG" "15")
; (c:DEMOPLAN_SETTINGS)
; (princ "DPWIN")
; (c:RCP_SETTINGS)
; (princ "RCPWIN")
; (c:EXST_RENAME)
; ; (princ "exst!")
; (c:demoOff)
;(c:nonplot_settings)
; (c:WALL_SETTINGS)
;(c:xrr)
;(c:nonplotOff)
;(c:bylall)
;(c:stb_settings)
; (command "LAYTHW")
; (command "LAYON")
; (command "_layer" "freeze" "*A-GRID*" "")
;(command "_layer" "thaw" "*A-GRID-PLAN-*" "")
; (command "_layer" "thaw" "*A-GRID-ELEV*" "")
;(setvar 'ctab (car(layoutlist)))
;(command "_mview" "fit" "")
;(command "_layer" "freeze" "*NorthArrow*" "")
;(c:por)
;(c:note_settings)
;(c:saveclose)
