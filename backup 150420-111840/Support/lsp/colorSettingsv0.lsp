(defun c:COLOR_SETTINGS ()
(command "_layer" "color" "5" "*A-DEMO" "")
(command "_layer" "color" "191" "*A-DEMO-WALL-PATT*" "")
(command "_layer" "color" "191" "*A-DEMO-PATT*" "")
(command "_layer" "color" "1" "*A-ANNO*" "")
(command "_layer" "color" "1" "*A-05*" "")
(command "_layer" "color" "40" "*A-13*" "")
(command "_layer" "color" "72" "*A-18*" "")
(command "_layer" "color" "140" "*A-25*" "")
(command "_layer" "color" "Blue" "*A-35*" "")
(command "_layer" "color" "182" "*A-50*" "")
(command "_layer" "color" "1" "*A-DOOR" "")
)
