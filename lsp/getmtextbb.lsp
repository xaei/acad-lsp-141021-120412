(defun GetMTextBB (Ent / EntData EnsPt TxtJust TxtWd TxtHt TxtRot LeftX RightX TopY BottomY)
; Get real Bounding Box for MText
; Tim Willey 03/2005
; Thanks to OLD-CADaver for the tips on the DXF codes

(setq EntData (entget Ent))
(setq InsPt (value 10 EntData))
(setq TxtJust (value 71 EntData))
(setq TxtWd (value 42 EntData))
(setq TxtHt (value 43 EntData))
(setq TxtRot (value 50 EntData))
(cond
((or (= TxtJust 1) (= TxtJust 4) (= TxtJust 7))
(setq LeftX (car InsPt))
(setq RightX (car (polar InsPt TxtRot TxtWd)))
)
((or (= TxtJust 2) (= TxtJust 5) (= TxtJust 8))
(setq LeftX (car (polar InsPt TxtRot (/ TxtWd 2))))
(setq RightX (car (polar InsPt (+ (DTR 180) TxtRot) (/ TxtWd 2))))
)
((or (= TxtJust 3) (= TxtJust 6) (= TxtJust 9))
(setq LeftX (car (polar InsPt (+ (DTR 180) TxtRot) TxtWd)))
(setq RightX (car InsPt))
)
)
(cond
((or (= TxtJust 1) (= TxtJust 2) (= TxtJust 3))
(setq TopY (cadr InsPt))
(setq BottomY (cadr (polar InsPt (+ (DTR 270) TxtRot) TxtHt)))
)
((or (= TxtJust 4) (= TxtJust 5) (= TxtJust 6))
(setq TopY (cadr (polar InsPt (+ (DTR 90) TxtRot) (/ TxtHt 2))))
(setq BottomY (cadr (polar InsPt (+ (DTR 270) TxtRot) (/ TxtHt 2))))
)
((or (= TxtJust 7) (= TxtJust 8) (= TxtJust 9))
(setq TopY (cadr (polar InsPt (+ (DTR 90) TxtRot) TxtHt)))
(setq BottomY (cadr InsPt))
)
)
(list (list LeftX BottomY) (list RightX BottomY) (list RightX TopY) (list LeftX TopY))
)
