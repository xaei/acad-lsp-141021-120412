(Defun C:AN ()
       (Setvar "Cmdecho" 0)
       (Setq A (Getint "\nStarting number: "))
       (Setq B (Getint "\nEnding number: "))
       (Setq P1 (Getpoint "\nStarting point: "))
       (Setq C (Getdist P1 "\nDistance between numbers: "))
       (Setq A1 (Getangle P1 "\nAngle to run numbers: "))
       (Setq D (Getvar "textsize"))
       (If (> A B)
           (Setq E -1)
           (Setq E 1)
       )
                (Repeat (+ 1 (Abs (- A B)))
                        (Setq F (Itoa A))
                        (Command "Text" P1 D 0 F)
                        (Setq A (+ A E))
                        (Setq P1 (Polar P1 A1 C))
                )
       (princ)
)
